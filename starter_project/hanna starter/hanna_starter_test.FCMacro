import FreeCAD
doc = FreeCAD.activeDocument()

# object_names = [obj.Name for obj in doc.Objects]
# print(object_names)


stand = doc.getObject('Body')
square = doc.getObject('Body001')


if stand:
	shape = stand.Shape
	vertices = shape.Vertexes
	faces = shape.Faces
	for vertex in vertices:
		print("Vertex:", vertex.X, vertex.Y, vertex.Z)
	else:
		print("Object not found")
	
	for face in faces:
		print("Face Area:", face.Area)
	else:
		print("Object not found")


if stand and square:
	if square.Shape.isInside(stand.Placement.Base,1.0,True):
		print("Square and Stand are touching or intersecting.")

	else:
		print("Square and Stand are not touching.")
else:
	print("One or both objects not found")
